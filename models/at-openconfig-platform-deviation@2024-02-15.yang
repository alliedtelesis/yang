module at-openconfig-platform-deviation {
  yang-version 1;
  namespace "http://alliedtelesis.com/ns/yang/at-openconfig-platform-deviation";
  prefix at-oc-plat-dev;

  import openconfig-platform {
    prefix oc-platform;
  }

  organization
    "Allied Telesis Labs Limited";

  contact
    "Allied Telesis Customer Support Group";

  description
    "This module contains deviation statements for the openconfig-platform module.";

  revision 2024-02-15 {
    description
      "Initial revision";
    reference
      "RFC 6020: YANG - A Data Modeling Language for the
       Network Configuration Protocol (NETCONF)";
  }

  deviation /oc-platform:components/oc-platform:component/oc-platform:config {
    deviate not-supported;
  }

  deviation /oc-platform:components/oc-platform:component/oc-platform:integrated-circuit {
    deviate not-supported;
  }

  deviation /oc-platform:components/oc-platform:component/oc-platform:state/oc-platform:mfg-name {
    deviate not-supported;
  }
  deviation /oc-platform:components/oc-platform:component/oc-platform:state/oc-platform:mfg-date {
    deviate not-supported;
  }
  deviation /oc-platform:components/oc-platform:component/oc-platform:state/oc-platform:firmware-version {
    deviate not-supported;
  }
  deviation /oc-platform:components/oc-platform:component/oc-platform:state/oc-platform:clei-code {
    deviate not-supported;
  }
  deviation /oc-platform:components/oc-platform:component/oc-platform:state/oc-platform:last-switchover-reason {
    deviate not-supported;
  }
  deviation /oc-platform:components/oc-platform:component/oc-platform:state/oc-platform:last-switchover-time {
    deviate not-supported;
  }
  deviation /oc-platform:components/oc-platform:component/oc-platform:state/oc-platform:last-reboot-reason {
    deviate not-supported;
  }
  deviation /oc-platform:components/oc-platform:component/oc-platform:state/oc-platform:last-reboot-time {
    deviate not-supported;
  }
  deviation /oc-platform:components/oc-platform:component/oc-platform:state/oc-platform:switchover-ready {
    deviate not-supported;
  }
  deviation /oc-platform:components/oc-platform:component/oc-platform:state/oc-platform:temperature {
    deviate not-supported;
  }
  deviation /oc-platform:components/oc-platform:component/oc-platform:state/oc-platform:memory {
    deviate not-supported;
  }
  deviation /oc-platform:components/oc-platform:component/oc-platform:state/oc-platform:allocated-power {
    deviate not-supported;
  }
  deviation /oc-platform:components/oc-platform:component/oc-platform:state/oc-platform:used-power {
    deviate not-supported;
  }
  deviation /oc-platform:components/oc-platform:component/oc-platform:state/oc-platform:pcie {
    deviate not-supported;
  }
  deviation /oc-platform:components/oc-platform:component/oc-platform:properties/oc-platform:property/oc-platform:config {
    deviate not-supported;
  }
  deviation /oc-platform:components/oc-platform:component/oc-platform:properties/oc-platform:property/oc-platform:name {
    deviate replace {
      type string;
      config false;
    }
  }
  deviation /oc-platform:components/oc-platform:component/oc-platform:subcomponents/oc-platform:subcomponent/oc-platform:config {
    deviate not-supported;
  }
  deviation /oc-platform:components/oc-platform:component/oc-platform:subcomponents/oc-platform:subcomponent/oc-platform:name {
    deviate replace {
      type string;
      config false;
    }
  }

  deviation /oc-platform:components/oc-platform:component/oc-platform:chassis {
    deviate not-supported;
  }
}
