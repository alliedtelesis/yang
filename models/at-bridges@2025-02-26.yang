module at-bridges {
  yang-version 1.1;
  namespace "http://alliedtelesis.com/ns/yang/at-bridges";
  prefix at-bridges;

  organization
    "Allied Telesis Labs New Zealand";

  contact
    "Allied Telesis Customer Support Group";

  description "This document defines a YANG module for
    Allied Telesis Bridges";

  revision 2025-02-26 {
    description "Allow comma separated vlan membership.";
    reference "3.0.0";
  }

  revision 2023-12-04 {
    description "Added support for AW+ platforms";
    reference "2.0.0";
  }

  revision 2020-05-28 {
    description "Initial revision.";
    reference
      "1.0.0

       RFC 6020: A Data Modeling Language for the
            Network Configuration Protocol (NETCONF)

       RFC 7950: The YANG 1.1 Data Modeling Language";
  }

  list bridges {
    key "name";
    description "Bridge List";
    leaf name {
      type string {
          pattern 'br(0|([1-9][0-9]?|[12][0-9]{2}|300))';
      }
      description "Bridge Name";
    }
    leaf l3-filtering {
      type boolean;
      default "false";
      description "L3 filtering on the bridge interface";
    }
    leaf mac-learning {
      type boolean;
      default "true";
      description "Dynamic learning of mac addresses";
    }
    leaf ageing-time {
      type uint32 {
        range "10..1000000";
      }
      default 300;
      description "Time(10-1000000 seconds) a learned mac address will persist after last update";
    }
    leaf flood-local {
      type boolean;
      default "false";
      description "Flood the local traffic on the bridge";
    }
    leaf vlan-filtering {
      type boolean;
      default "false";
      description "Filter traffic to/from ports based on the VID";
    }
    list ports {
      key "name";
      description "Members of this bridge group";
      leaf name {
        type string;
        description "Port name";
      }
      leaf protected {
        type boolean;
        default "false";
        description "Port protected mode";
      }
      leaf vid {
        type string {
          pattern '(((^|[,])((([1-9][0-9]{0,2}|[1-3][0-9]{3}|40[0-8][0-9]|409[0-4])-([1-9][0-9]{0,2}|[1-3][0-9]{3}|40[0-8][0-9]|409[0-4]))|([1-9][0-9]{0,2}|[1-3][0-9]{3}|40[0-8][0-9]|409[0-4])))+)';
        }
        default "1-4094";
        description "VLAN Membership (comma separated list of numbers(1..4094) or ranges(1..4094-1..4094))";
      }
      leaf pvid {
        type uint32 {
          range "1..4094";
        }
        default 1;
        description "Native VLAN (1..4094)";
      }
    }
    list mac-entries {
      key "id";
      config false;
      description "FDB entries for this bridge";
      leaf id {
        type uint32;
        description "the index of the FDB entry";
      }
      leaf mac-address {
        type string;
        description "MAC address learned";
      }
      leaf port-name {
        type uint32;
        description "Port name associated with the MAC address";
      }
      leaf is-local {
        type boolean;
        description "MAC address is locally connected to the port";
      }
      leaf ageing-timer {
        type uint32;
        description "How long the MAC address has been present on the port";
      }
    }
  }
}
