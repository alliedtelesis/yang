module at-softwire-ce {
  yang-version 1.1;
  namespace "http://alliedtelesis.com/ns/yang/at-softwire-ce";
  prefix at-softwire-ce;

  import ietf-inet-types {
    prefix inet;
    reference "Section 4 of RFC 6991";
  }

  import at-softwire-common {
    prefix at-softwire-common;
    reference
      "RFC 8676: YANG Modules for IPv4-in-IPv6 Address plus Port
                 Softwires";
  }

  organization
    "IETF Softwire Working Group";

  contact
    "WG Web:   <https://datatracker.ietf.org/wg/softwire/>
     WG List:  <mailto:softwire@ietf.org>

     Author:  Qi Sun
              <mailto:sunqi.ietf@gmail.com>

     Author:  Linhui Sun
              <mailto:lh.sunlinh@gmail.com>

     Author:  Yong Cui
              <mailto:yong@csnet1.cs.tsinghua.edu.cn>

     Author:  Ian Farrer
              <mailto:ian.farrer@telekom.de>

     Author:  Sladjana Zoric
              <mailto:sladjana.zoric@telekom.de>

     Author:  Mohamed Boucadair
              <mailto:mohamed.boucadair@orange.com>

     Author:  Rajiv Asati
               <mailto:rajiva@cisco.com>";
  description
    "This document defines a YANG module for the configuration and
     management of A+P Softwire Customer Premises Equipment (CEs). It
     covers Lightweight 4over6, MAP-E, and MAP-T mechanisms.

     Copyright (c) 2018 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 8676; see
     the RFC itself for full legal notices.";

  revision 2023-06-21 {
    description
      "Added ATL counters for interactions with VNE servers";
    reference
      "ER-5478 MAP-E Error Counters";
  }

  revision 2018-10-23 {
    description
      "Initial revision.";
    reference
      "RFC 8676: YANG Modules for IPv4-in-IPv6 Address plus Port
                 Softwires";
  }

  /*
   * Features
   */

  feature binding-mode {
    description
      "Binding is used for configuring the Lightweight 4over6 mechanism.

       Binding based softwire mechanisms are IPv4-over-IPv6 tunnelling
       transition mechanisms specifically intended for complete
       independence between the IPv6 subnet prefix (and IPv6 address)
       and IPv4 address, with or without IPv4 address sharing.

       This is accomplished by maintaining state for each softwire
       (per-subscriber state) in the central Border Relay (BR) and using
       a hub-and-spoke forwarding architecture. In order to delegate the
       NAPT function and achieve IPv4 address sharing, port-restricted
       IPv4 addresses needs to be allocated to CEs.

       This feature indicates that the network element can function as
       one or more binding based softwire instances.";
    reference
      "RFC7596: Lightweight 4over6: An Extension to the Dual-Stack Lite
                Architecture
       RFC7597: Mapping of Address and Port with Encapsulation (MAP-E)
       RFC7599: Mapping of Address and Port using Translation (MAP-T)";
  }

  feature map-e {
    description
      "MAP-E is an IPv6 transition mechanism for transporting IPv4
       packets across an IPv6 network using IP encapsulation. MAP-E
       allows for a reduction of the amount of centralized state using
       rules to express IPv4/IPv6 address mappings. This introduces an
       algorithmic relationship between the IPv6 subnet and IPv4
       address.

       This feature indicates that the network element can function as
       one or more MAP-E softwire instances.";
    reference
      "RFC7597: Mapping of Address and Port with Encapsulation (MAP-E)";
  }

  feature map-t {
    description
      "MAP-T is an IPv6 transition mechanism for transporting IPv4
       packets across an IPv6 network using IP translation. It leverages
       a double stateless NAT64 based solution as well as the stateless
       algorithmic address & transport layer port mapping algorithm
       defined for MAP-E.

       This feature indicates that the network element can function as
       one or more MAP-T softwire instances.";
    reference
      "RFC7599: Mapping of Address and Port using Translation (MAP-T)";
  }

  // Binding Entry

  grouping binding-entry {
    description
      "The binding BR (Border Relay) maintains an address binding table
       that contains the binding between the CE's IPv6 address,
       the allocated IPv4 address and restricted port-set.";
    leaf binding-ipv6info {
      type union {
        type inet:ipv6-address;
        type inet:ipv6-prefix;
      }
      description
        "The IPv6 information for a binding entry.

         When the IPv6 prefix type is used,
         the IPv6 source address of the CE is constructed
         according to the description in RFC7596.

         If the IPv6 address type is used, the CE can use
         any valid /128 address from a prefix assigned to
         the CE.";
      reference "Section 5.1 of RFC7596.";
    }
    /*
     * Added new leaf binding-ipv4-addr
     */
    leaf binding-ipv4-addr {
      type inet:ipv4-address;
      description
        "The IPv4 address assigned to the binding CE,
         which is used as the IPv4 external address
         for binding CE local NAPT44.";
    }
    /*
     * Added this container for the port set parameters
     */
    container port-set {
      description
        "Describes a set of layer 4 port numbers.
         This may be a simple port range, or use the Port Set
         Identifier (PSID) algorithm to represent a range of transport
         layer ports which will be used by a NAPT.";
      leaf psid-offset {
        type uint8 {
          range "0..16";
        }
        description
          "The number of offset bits. In Lightweight 4over6,
           the default value is 0 for assigning one contiguous
           port range. In MAP-E/T, the default value is 6,
           which means the system ports (0-1023) are excluded by
           default and the assigned port ranges are distributed across
           the entire port space, depending on either psid-len or the
           number of contiguous ports.";
      }
      leaf psid-len {
        type uint8 {
          range "0..15";
        }
        mandatory true;
        description
          "The length of PSID, representing the sharing
           ratio for an IPv4 address. This, along with ea-len, can
           be used to calculate the number of contiguous ports per
           port range";
      }
      leaf psid {
        type uint16;
        mandatory true;
        description
          "Port Set Identifier (PSID) value, which
           identifies a set of ports algorithmically.";
      }
    }
    leaf br-ipv6-addr {
      type inet:ipv6-address;
      mandatory true;
      description
        "The IPv6 address of the binding BR.";
    }
  }

  // configuration and stateful parameters for softwire CE interface
  container softwire {
    description "Softwire interface configuration";

    list sw-instance {
      key "name";

      description "Softwire CE interface configuration";

      leaf name {
        type string;
        mandatory true;
        description
          "The name of MAP";
      }

      leaf softwire-payload-mtu {
        type uint16;
        units "bytes";
        description
          "The payload IPv4 MTU for the softwire tunnel.";
      }
      leaf softwire-path-mru {
        type uint16;
        units "bytes";
        description
          "The path MRU for the softwire (payload + encapsulation
           overhead).";
        reference
          "RFC 4213: Basic Transition Mechanisms for IPv6 Hosts and
                   Routers";
      }

      leaf rule-source {
        type string;
        mandatory true;
        description
          "The map rule source: e.g. dhcp, proprietary, static";
      }

      leaf vendor {
        type string;
        description
          "The vendor name of rule source";
      }

      leaf vendor-userid {
        type string;
        description
          "The user identifier for the vendor of rule source";
      }

      leaf upstream-interface {
        type string;
        description
         "The upstream interface";
      }

      choice ce-type {
        description
          "Sets the softwire CE mechanism";

        case binding {
          if-feature "binding-mode";
          description
            "CE binding configuration";
          uses binding-entry;
        }

        case algo {
          if-feature "map-e or map-t";
          description
            "CE algorithm configuration";

          choice data-plane {
            description "Selects MAP-E (encapsulation) or MAP-T
            (translation)";
            case encapsulation {
              description "encapsulation for MAP-E";
              leaf br-ipv6-full-addr {
                type inet:ipv6-address;
                mandatory true;
                description
                  "The IPv6 address of the MAP-E BR.";
              }
            }
            case translation {
              description "translation for MAP-T";
              leaf dmr-ipv6-prefix {
                type inet:ipv6-prefix;
                description
                  "The IPv6 prefix of the MAP-T BR.";
              }
            }
          }

          leaf ipv6-fixlen {
            type uint32;
            description
              "Reply address length (30-64) to end-users";
          }

          leaf map-version {
            type string;
            mandatory true;
            description
              "The map version: RFC (7597/RFC7599) or DRAFT3 of RFC7597";
          }

          leaf mesh-mode {
            type boolean;
            description
              "Enable / disable mesh mode";
          }

          container algo-instances {
            description
              "Collection of MAP-E/MAP-T parameters";
            list algo-instance {
              key "id";
              description
                "MAP forwarding rule instance for
                 MAP-E/MAP-T";
              leaf id {
                type uint32;
                mandatory true;
                description "Algorithm Instance ID";
              }
              uses at-softwire-common:algorithm-instance;
            }
          }
        }
      }
    }

    container statistics {
      config false;
      description "Statistics for interactions with VNE servers";
      container general {
        description "General counters for event when interacting with VNE servers.";
        leaf auth-fail {
          type uint64;
          description
            "Failure to communicate with MAP rule server due to a authentication failure.";
        }

        leaf mem-alloc-fail-server {
          type uint64;
          description
            "Failure to allocate memory to process response from VNE server.";
        }

        leaf unknown-rule-state {
          type uint64;
          description
            "Unknown rule state.";
        }

        leaf unknown-com-fail-server {
          type uint64;
          description
            "Failure to communicate with MAP rule server for an unknown reason.";
        }

        leaf bad-format-resp-server {
          type uint64;
          description
            "Response from VNE server was incorrectly formatted and couldn't be processed.";
        }

        leaf bad-data-resp-server {
          type uint64;
          description
            "Response from VNE server was missing data or contained an invalid id.";
        }

        leaf no-ipv6-match-resp-server {
          type uint64;
          description
            "None of the supplied rules matched our IPv6 address.";
        }

        leaf com-fail-server {
          type uint64;
          description
            "Failed to communicate with MAP rule server.";
        }

        leaf mem-alloc-fail-hgw {
          type uint64;
          description
            "Failure to allocate memory to process response from HGW.";
        }

        leaf rule-retrieve-sleep-start {
          type uint64;
          description
            "Commencing sleep until next rule retrieval attempt";
        }

        leaf def-sleep-range {
          type uint64;
          description
            "Using default sleep interval range";
        }

        leaf def-startup-sleep-range {
          type uint64;
          description
            "Using default startup sleep interval";
        }
      }
      container svrtxrx {
        description "MAP Rule Server Tx/Rx";
        leaf rule-req-tx {
          type uint64;
          description
            "MAP rule request transmitted";
        }

        leaf rule-resp-rx-success {
          type uint64;
          description
            "MAP rule server responded with success (2xx)";
        }

        leaf rule-resp-rx-fail-300 {
          type uint64;
          description
            "MAP rule server responded with error 3xx";
        }

        leaf rule-resp-rx-fail-400 {
          type uint64;
          description
            "MAP rule server responded with error 4xx";
        }

        leaf rule-resp-rx-fail-500 {
          type uint64;
          description
            "MAP rule server responded with error 5xx";
        }

        leaf rule-resp-rx-timeout {
          type uint64;
          description
            "MAP rule server request timed out";
        }

        leaf rule-resp-rx-fail-unknown {
          type uint64;
          description
            "MAP rule server request failed (unknown reason)";
        }
      }
      container authtxrx {
        description "Authentication Server Tx/Rx";
        leaf auth-req-tx {
          type uint64;
          description
            "Authentication request transmitted";
        }

        leaf auth-resp-rx-good {
          type uint64;
          description
            "Authentication server responded 'good'";
        }

        leaf auth-resp-rx-nochg {
          type uint64;
          description
            "Authentication server responded 'nochg'";
        }

        leaf auth-resp-rx-nohost {
          type uint64;
          description
            "Authentication server responded 'nohost'";
        }

        leaf auth-resp-rx-911 {
          type uint64;
          description
            "Authentication server responded '911'";
        }

        leaf auth-resp-rx-timeout {
          type uint64;
          description
            "Authentication request timed out";
        }

        leaf auth-resp-rx-fail-other {
          type uint64;
          description
            "Authentication request failed (other reason)";
        }
      }
      container hgw {
        description "Hardware Gateway Response";
        leaf hgw-resp-active {
          type uint64;
          description
            "Hardware Gateway active";
        }

        leaf hgw-resp-inactive {
          type uint64;
          description
            "Hardware Gateway inactive/no response";
        }

        leaf hgw-status {
          type enumeration {
            enum active {
              value 0;
              description "HGW is active and managing MAP-E";
            }
            enum inactive {
              value 1;
              description "HGW is inactive and not managing MAP-E";
            }
          }
          default inactive;
          description "Most recent HGW Status result";
        }
      }
    }
  }
}
