module at-ietf-interfaces-deviation {
  yang-version 1;
  namespace "http://alliedtelesis.com/ns/yang/at-ietf-interfaces-deviation";
  prefix at-if;

  import ietf-interfaces {
    prefix if;
  }

  import iana-if-type {
    prefix ianaift;
  }

  organization
    "Allied Telesis Labs Limited";

  contact
    "Allied Telesis Customer Support Group";

  description
    "This module contains deviation statements for the ietf-interfaces module.";

  revision 2024-10-01 {
    description
      "Set the identityref of interface if:type to ianaift:iana-interface-type.
       Add patterns for interface name and description. These are fairly
       generic patterns, and for interface name in particular should not
       be taken as indicative of how valid interface names should be
       formatted.";
  }
  revision 2024-02-14 {
    description
      "Remove not-supported for interfaces-state";
  }
  revision 2023-07-10 {
    description
      "Initial revision";
    reference
      "RFC 6020: YANG - A Data Modeling Language for the
       Network Configuration Protocol (NETCONF)";
  }

  deviation "/if:interfaces/if:interface/if:name" {
    deviate replace {
      type string {
        pattern "[a-z][a-z0-9.]+";
      }
    }
  }

  deviation "/if:interfaces/if:interface/if:description" {
    deviate replace {
      type string {
        pattern "[ -~]{1,768}";
      }
    }
  }

  deviation "/if:interfaces/if:interface/if:type" {
    deviate replace {
      config false;
      type identityref {
        base ianaift:iana-interface-type;
      }
    }
  }
  deviation "/if:interfaces/if:interface/if:enabled" {
    deviate replace {
      type boolean;
      default "true";
    }
    description
      "This leaf contains the configured, desired state of the
       interface.

       Systems that implement the IF-MIB use the value of this
       leaf in the intended configuration to set
       IF-MIB.ifAdminStatus to 'up' or 'down' after an ifEntry
       has been initialized, as described in RFC 2863.

       Changes in this leaf in the intended configuration are
       reflected in ifAdminStatus. Changes in ifAdminStatus by
       other means are reflected in this leaf.";
  }
  deviation "/if:interfaces-state/if:interface/if:type" {
    deviate replace {
      config false;
      type identityref {
        base ianaift:iana-interface-type;
      }
    }
  }
}
