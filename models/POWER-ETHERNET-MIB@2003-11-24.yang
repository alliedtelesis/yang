/*
 * This YANG module has been generated by smidump 0.5.0:
 *
 *      smidump -f yang POWER-ETHERNET-MIB
 *
 * Do not edit. Edit the source file instead!
 */

module POWER-ETHERNET-MIB {

  namespace "urn:ietf:params:xml:ns:yang:smiv2:POWER-ETHERNET-MIB";
  prefix POWER-ETHERNET-MIB;

  import SNMP-FRAMEWORK-MIB {
    prefix "snmp-framework";
  }

  import ietf-yang-smiv2 {
    prefix "smiv2";
  }

  import ietf-yang-types {
    prefix "yang";
  }

  organization
   "IETF Ethernet Interfaces and Hub MIB
    Working Group";

  contact
   "
    WG Charter:
    http://www.ietf.org/html.charters/hubmib-charter.html

    Mailing lists:
    General Discussion: hubmib@ietf.org
    To Subscribe: hubmib-requests@ietf.org
    In Body: subscribe your_email_address

    Chair: Dan Romascanu
    Avaya
    Tel:  +972-3-645-8414
    Email: dromasca@avaya.com

    Editor: Avi Berger
    PowerDsine Inc.
    Tel:    972-9-7755100 Ext 307
    Fax:    972-9-7755120
    E-mail: avib@PowerDsine.com";

  description
   "The MIB module for managing Power Source Equipment
    (PSE) working according to the IEEE 802.af Powered
    Ethernet (DTE Power via MDI) standard.

     The following terms are used throughout this
     MIB module.  For complete formal definitions,
     the IEEE 802.3 standards should be consulted
     wherever possible:

     Group - A recommended, but optional, entity
     defined by the IEEE 802.3 management standard,
     in order to support a modular numbering scheme.
     The classical example allows an implementor to
     represent field-replaceable units as groups of
     ports, with the port numbering matching the
     modular hardware implementation.

    Port - This entity identifies the port within the group
    for which this entry contains information.  The numbering
    scheme for ports is implementation specific.

    Copyright (c) The Internet Society (2003).  This version
    of this MIB module is part of RFC 3621; See the RFC
    itself for full legal notices.";

  revision 2003-11-24 {
    description
     "Initial version, published as RFC 3621.";
  }


  container POWER-ETHERNET-MIB {
    config false;

    container pethPsePortTable {
      description
       "A table of objects that display and control the power
        characteristics of power Ethernet ports on a Power Source
        Entity (PSE) device.  This group will be implemented in
        managed power Ethernet switches and mid-span devices.
        Values of all read-write objects in this table are
        persistent at restart/reboot.";
      smiv2:oid "1.3.6.1.2.1.105.1.1";

      list pethPsePortEntry {
        key "pethPsePortGroupIndex pethPsePortIndex";
        description
         "A set of objects that display and control the power
          characteristics of a power Ethernet PSE port.";
        smiv2:oid "1.3.6.1.2.1.105.1.1.1";

        leaf pethPsePortGroupIndex {
          type int32 {
            range "1..2147483647";
          }
          description
           "This variable uniquely identifies the group
            containing the port to which a power Ethernet PSE is
            connected.  Group means box in the stack, module in a
            rack and the value 1 MUST be used for non-modular devices.
            Furthermore, the same value MUST be used in this variable,
            pethMainPseGroupIndex, and pethNotificationControlGroupIndex
            to refer to a given box in a stack or module in the rack.";
          smiv2:max-access "not-accessible";
          smiv2:oid "1.3.6.1.2.1.105.1.1.1.1";
        }

        leaf pethPsePortIndex {
          type int32 {
            range "1..2147483647";
          }
          description
           "This variable uniquely identifies the power Ethernet PSE
            port within group pethPsePortGroupIndex to which the
            power Ethernet PSE entry is connected.";
          smiv2:max-access "not-accessible";
          smiv2:oid "1.3.6.1.2.1.105.1.1.1.2";
        }

        leaf pethPsePortAdminEnable {
          type boolean;
          description
           "true (1) An interface which can provide the PSE functions.
            false(2) The interface will act as it would if it had no PSE
            function.";
          reference
           "IEEE Std 802.3af Section 30.9.1.1.2 aPSEAdminState";
          smiv2:max-access "read-write";
          smiv2:oid "1.3.6.1.2.1.105.1.1.1.3";
        }

        leaf pethPsePortPowerPairsControlAbility {
          type boolean;
          description
           "Describes the capability of controlling the power pairs
            functionality to switch pins for sourcing power.
            The value true indicate that the device has the capability
            to control the power pairs.  When false the PSE Pinout
            Alternative used cannot be controlled through the
            PethPsePortAdminEnable attribute.";
          reference
           "IEEE Std 802.3af Section 30.9.1.1.3
            aPSEPowerPairsControlAbility";
          smiv2:max-access "read-only";
          smiv2:oid "1.3.6.1.2.1.105.1.1.1.4";
        }

        leaf pethPsePortPowerPairs {
          type enumeration {
            enum "signal" {
              value "1";
            }
            enum "spare" {
              value "2";
            }
          }
          description
           "Describes or controls the pairs in use.  If the value of
            pethPsePortPowerPairsControl is true, this object is
            writable.
            A value of signal(1) means that the signal pairs
            only are in use.
            A value of spare(2) means that the spare pairs
            only are in use.";
          reference
           "IEEE Std 802.3af Section 30.9.1.1.4 aPSEPowerPairs";
          smiv2:max-access "read-write";
          smiv2:oid "1.3.6.1.2.1.105.1.1.1.5";
        }

        leaf pethPsePortDetectionStatus {
          type enumeration {
            enum "disabled" {
              value "1";
            }
            enum "searching" {
              value "2";
            }
            enum "deliveringPower" {
              value "3";
            }
            enum "fault" {
              value "4";
            }
            enum "test" {
              value "5";
            }
            enum "otherFault" {
              value "6";
            }
          }
          description
           "Describes the operational status of the port PD detection.
            A value of disabled(1)- indicates that the PSE State diagram
            is in the state DISABLED.
            A value of deliveringPower(3) - indicates that the PSE State
            diagram is in the state POWER_ON for a duration greater than
            tlim max (see IEEE Std 802.3af Table 33-5 tlim).
            A value of fault(4) - indicates that the PSE State diagram is
            in the state TEST_ERROR.
            A value of test(5) - indicates that the PSE State diagram is
            in the state TEST_MODE.
            A value of otherFault(6) - indicates that the PSE State
            diagram is in the state IDLE due to the variable
            error_conditions.
            A value of searching(2)- indicates the PSE State diagram is
            in a state other than those listed above.";
          reference
           "IEEE Std 802.3af Section 30.9.1.1.5
            aPSEPowerDetectionStatus";
          smiv2:max-access "read-only";
          smiv2:oid "1.3.6.1.2.1.105.1.1.1.6";
        }

        leaf pethPsePortPowerPriority {
          type enumeration {
            enum "critical" {
              value "1";
            }
            enum "high" {
              value "2";
            }
            enum "low" {
              value "3";
            }
          }
          description
           "This object controls the priority of the port from the point
            of view of a power management algorithm.  The priority that
            is set by this variable could be used by a control mechanism
            that prevents over current situations by disconnecting first
            ports with lower power priority.  Ports that connect devices
            critical to the operation of the network - like the E911
            telephones ports - should be set to higher priority.";
          smiv2:max-access "read-write";
          smiv2:oid "1.3.6.1.2.1.105.1.1.1.7";
        }

        leaf pethPsePortMPSAbsentCounter {
          type yang:counter32;
          description
           "This counter is incremented when the PSE state diagram
            transitions directly from the state POWER_ON to the
            state IDLE due to tmpdo_timer_done being asserted.";
          reference
           "IEEE Std 802.3af Section 30.9.1.1.11
            aPSEMPSAbsentCounter";
          smiv2:max-access "read-only";
          smiv2:oid "1.3.6.1.2.1.105.1.1.1.8";
        }

        leaf pethPsePortType {
          type snmp-framework:SnmpAdminString;
          description
           "A manager will set the value of this variable to indicate
            the type of powered device that is connected to the port.
            The default value supplied by the agent if no value has
            ever been set should be a zero-length octet string.";
          smiv2:max-access "read-write";
          smiv2:oid "1.3.6.1.2.1.105.1.1.1.9";
        }

        leaf pethPsePortPowerClassifications {
          type enumeration {
            enum "class0" {
              value "1";
            }
            enum "class1" {
              value "2";
            }
            enum "class2" {
              value "3";
            }
            enum "class3" {
              value "4";
            }
            enum "class4" {
              value "5";
            }
          }
          description
           "Classification is a way to tag different terminals on the
            Power over LAN network according to their power consumption.
            Devices such as IP telephones, WLAN access points and others,
            will be classified according to their power requirements.

            The meaning of the classification labels is defined in the
            IEEE specification.

            This variable is valid only while a PD is being powered,
            that is, while the attribute pethPsePortDetectionStatus
            is reporting the enumeration deliveringPower.";
          reference
           "IEEE Std 802.3af Section 30.9.1.1.6
            aPSEPowerClassification";
          smiv2:max-access "read-only";
          smiv2:oid "1.3.6.1.2.1.105.1.1.1.10";
        }

        leaf pethPsePortInvalidSignatureCounter {
          type yang:counter32;
          description
           "This counter is incremented when the PSE state diagram
            enters the state SIGNATURE_INVALID.";
          reference
           "IEEE Std 802.3af Section 30.9.1.1.7
            aPSEInvalidSignatureCounter";
          smiv2:max-access "read-only";
          smiv2:oid "1.3.6.1.2.1.105.1.1.1.11";
        }

        leaf pethPsePortPowerDeniedCounter {
          type yang:counter32;
          description
           "This counter is incremented when the PSE state diagram
            enters the state POWER_DENIED.";
          reference
           "IEEE Std 802.3af Section 30.9.1.1.8
            aPSEPowerDeniedCounter";
          smiv2:max-access "read-only";
          smiv2:oid "1.3.6.1.2.1.105.1.1.1.12";
        }

        leaf pethPsePortOverLoadCounter {
          type yang:counter32;
          description
           "This counter is incremented when the PSE state diagram
            enters the state ERROR_DELAY_OVER.";
          reference
           "IEEE Std 802.3af Section 30.9.1.1.9
            aPSEOverLoadCounter";
          smiv2:max-access "read-only";
          smiv2:oid "1.3.6.1.2.1.105.1.1.1.13";
        }

        leaf pethPsePortShortCounter {
          type yang:counter32;
          description
           "This counter is incremented when the PSE state diagram
            enters the state ERROR_DELAY_SHORT.";
          reference
           "IEEE Std 802.3af Section 30.9.1.1.10
            aPSEShortCounter";
          smiv2:max-access "read-only";
          smiv2:oid "1.3.6.1.2.1.105.1.1.1.14";
        }
      }
    }

    container pethMainPseTable {
      description
       "A table of objects that display and control attributes
        of the main power source in a PSE  device.  Ethernet
        switches are one example of boxes that would support
        these objects.
        Values of all read-write objects in this table are
        persistent at restart/reboot.";
      smiv2:oid "1.3.6.1.2.1.105.1.3.1";

      list pethMainPseEntry {
        key "pethMainPseGroupIndex";
        description
         "A set of objects that display and control the Main
          power of a PSE. ";
        smiv2:oid "1.3.6.1.2.1.105.1.3.1.1";

        leaf pethMainPseGroupIndex {
          type int32 {
            range "1..2147483647";
          }
          description
           "This variable uniquely identifies the group to which
            power Ethernet PSE is connected.  Group means (box in
            the stack, module in a rack) and the value 1 MUST be
            used for non-modular devices.  Furthermore, the same
            value MUST be used in this variable, pethPsePortGroupIndex,
            and pethNotificationControlGroupIndex to refer to a
            given box in a stack or module in a rack.";
          smiv2:max-access "not-accessible";
          smiv2:oid "1.3.6.1.2.1.105.1.3.1.1.1";
        }

        leaf pethMainPsePower {
          type yang:gauge32 {
            range "1..65535";
          }
          units "Watts";
          description
           "The nominal power of the PSE expressed in Watts.";
          smiv2:max-access "read-only";
          smiv2:oid "1.3.6.1.2.1.105.1.3.1.1.2";
        }

        leaf pethMainPseOperStatus {
          type enumeration {
            enum "on" {
              value "1";
            }
            enum "off" {
              value "2";
            }
            enum "faulty" {
              value "3";
            }
          }
          description
           "The operational status of the main PSE.";
          smiv2:max-access "read-only";
          smiv2:oid "1.3.6.1.2.1.105.1.3.1.1.3";
        }

        leaf pethMainPseConsumptionPower {
          type yang:gauge32;
          units "Watts";
          description
           "Measured usage power expressed in Watts.";
          smiv2:max-access "read-only";
          smiv2:oid "1.3.6.1.2.1.105.1.3.1.1.4";
        }

        leaf pethMainPseUsageThreshold {
          type int32 {
            range "1..99";
          }
          units "%";
          description
           "The usage threshold expressed in percents for
            comparing the measured power and initiating
            an alarm if the threshold is exceeded.";
          smiv2:max-access "read-write";
          smiv2:oid "1.3.6.1.2.1.105.1.3.1.1.5";
        }
      }
    }

    container pethNotificationControlTable {
      description
       "A table of objects that display and control the
        Notification on a PSE  device.
        Values of all read-write objects in this table are
        persistent at restart/reboot.";
      smiv2:oid "1.3.6.1.2.1.105.1.4.1";

      list pethNotificationControlEntry {
        key "pethNotificationControlGroupIndex";
        description
         "A set of objects that control the Notification events.";
        smiv2:oid "1.3.6.1.2.1.105.1.4.1.1";

        leaf pethNotificationControlGroupIndex {
          type int32 {
            range "1..2147483647";
          }
          description
           "This variable uniquely identifies the group.  Group
            means box in the stack, module in a rack and the value
            1 MUST be used for non-modular devices.  Furthermore,
            the same value MUST be used in this variable,
            pethPsePortGroupIndex, and
            pethMainPseGroupIndex to refer to a given box in a
            stack or module in a rack. ";
          smiv2:max-access "not-accessible";
          smiv2:oid "1.3.6.1.2.1.105.1.4.1.1.1";
        }

        leaf pethNotificationControlEnable {
          type boolean;
          description
           "This object controls, on a per-group basis, whether
            or not notifications from the agent are enabled.  The
            value true(1) means that notifications are enabled; the
            value false(2) means that they are not.";
          smiv2:max-access "read-write";
          smiv2:oid "1.3.6.1.2.1.105.1.4.1.1.2";
        }
      }
    }
  }

  notification pethPsePortOnOffNotification {
    description
     " This Notification indicates if Pse Port is delivering or
      not power to the PD.  This Notification SHOULD be sent on
      every status change except in the searching mode.
      At least 500 msec must elapse between notifications
      being emitted by the same object instance.";
    smiv2:oid "1.3.6.1.2.1.105.0.1";

    container object-1 {

      leaf pethPsePortGroupIndex {
        type leafref {
          path "/POWER-ETHERNET-MIB:POWER-ETHERNET-MIB/POWER-ETHERNET-MIB:pethPsePortTable/POWER-ETHERNET-MIB:pethPsePortEntry/POWER-ETHERNET-MIB:pethPsePortGroupIndex";
        }
      }

      leaf pethPsePortIndex {
        type leafref {
          path "/POWER-ETHERNET-MIB:POWER-ETHERNET-MIB/POWER-ETHERNET-MIB:pethPsePortTable/POWER-ETHERNET-MIB:pethPsePortEntry/POWER-ETHERNET-MIB:pethPsePortIndex";
        }
      }

      leaf pethPsePortDetectionStatus {
        type leafref {
          path "/POWER-ETHERNET-MIB:POWER-ETHERNET-MIB/POWER-ETHERNET-MIB:pethPsePortTable/POWER-ETHERNET-MIB:pethPsePortEntry/POWER-ETHERNET-MIB:pethPsePortDetectionStatus";
        }
      }
    }
  }

  notification pethMainPowerUsageOnNotification {
    description
     " This Notification indicate PSE Threshold usage
      indication is on, the usage power is above the
      threshold.  At least 500 msec must elapse between
      notifications being emitted by the same object
      instance.";
    smiv2:oid "1.3.6.1.2.1.105.0.2";

    container object-1 {

      leaf pethMainPseGroupIndex {
        type leafref {
          path "/POWER-ETHERNET-MIB:POWER-ETHERNET-MIB/POWER-ETHERNET-MIB:pethMainPseTable/POWER-ETHERNET-MIB:pethMainPseEntry/POWER-ETHERNET-MIB:pethMainPseGroupIndex";
        }
      }

      leaf pethMainPseConsumptionPower {
        type leafref {
          path "/POWER-ETHERNET-MIB:POWER-ETHERNET-MIB/POWER-ETHERNET-MIB:pethMainPseTable/POWER-ETHERNET-MIB:pethMainPseEntry/POWER-ETHERNET-MIB:pethMainPseConsumptionPower";
        }
      }
    }
  }

  notification pethMainPowerUsageOffNotification {
    description
     " This Notification indicates PSE Threshold usage indication
      off, the usage power is below the threshold.
      At least 500 msec must elapse between notifications being
      emitted by the same object instance.";
    smiv2:oid "1.3.6.1.2.1.105.0.3";

    container object-1 {

      leaf pethMainPseGroupIndex {
        type leafref {
          path "/POWER-ETHERNET-MIB:POWER-ETHERNET-MIB/POWER-ETHERNET-MIB:pethMainPseTable/POWER-ETHERNET-MIB:pethMainPseEntry/POWER-ETHERNET-MIB:pethMainPseGroupIndex";
        }
      }

      leaf pethMainPseConsumptionPower {
        type leafref {
          path "/POWER-ETHERNET-MIB:POWER-ETHERNET-MIB/POWER-ETHERNET-MIB:pethMainPseTable/POWER-ETHERNET-MIB:pethMainPseEntry/POWER-ETHERNET-MIB:pethMainPseConsumptionPower";
        }
      }
    }
  }

  smiv2:alias "powerEthernetMIB" {
    smiv2:oid "1.3.6.1.2.1.105";
  }

  smiv2:alias "pethNotifications" {
    smiv2:oid "1.3.6.1.2.1.105.0";
  }

  smiv2:alias "pethObjects" {
    smiv2:oid "1.3.6.1.2.1.105.1";
  }

  smiv2:alias "pethMainPseObjects" {
    smiv2:oid "1.3.6.1.2.1.105.1.3";
  }

  smiv2:alias "pethNotificationControl" {
    smiv2:oid "1.3.6.1.2.1.105.1.4";
  }

  smiv2:alias "pethConformance" {
    smiv2:oid "1.3.6.1.2.1.105.2";
  }

  smiv2:alias "pethCompliances" {
    smiv2:oid "1.3.6.1.2.1.105.2.1";
  }

  smiv2:alias "pethGroups" {
    smiv2:oid "1.3.6.1.2.1.105.2.2";
  }

}
