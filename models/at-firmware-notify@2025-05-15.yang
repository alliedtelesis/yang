module at-firmware-notify {
    yang-version 1.1;
    namespace "http://alliedtelesis.com/ns/yang/at-firmware-update";
    prefix at-firmware-update;

    organization
        "Allied Telesis Labs New Zealand";

    contact
        "Allied Telesis Customer Support Group";

    description "This document defines a YANG module for
        Allied Telesis Firmware Update";

    revision 2025-05-15 {
      description "Initial revision";
          reference
            "1.0.0

            RFC 6020: A Data Modeling Language for the
                    Network Configuration Protocol (NETCONF)

            RFC 7950: The YANG 1.1 Data Modeling Language";
    }

    container firmware-update {
        description "Firmware Update";

        leaf firmware-notify-interval {
            description "Notify interval for firmware maintenance releases, in minutes";
            type uint64;
            default "1440";
        }

        leaf available-firmware {
            description "Human-readable string of latest available firmware release";
            type string;
            mandatory false;
        }

        leaf current-firmware {
            description "Human-readble string of firmware currently in use";
            type string;
            mandatory false;
        }

        leaf update-available {
            description "Indicates that a firmware-update is available";
            type boolean;
            default false;
        }
    }
}
