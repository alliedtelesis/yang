module at-openconfig-interfaces-deviation {
  yang-version 1;
  namespace "http://alliedtelesis.com/ns/yang/at-openconfig-interfaces-deviation";
  prefix at-oc-if;

  import openconfig-interfaces {
    prefix oc-if;
  }

  organization
    "Allied Telesis Labs Limited";

  contact
    "Allied Telesis Customer Support Group";

  description
    "This module contains deviation statements for the openconfig-interfaces module.";

  revision 2023-07-10 {
    description
      "Initial revision";
    reference
      "RFC 6020: YANG - A Data Modeling Language for the
       Network Configuration Protocol (NETCONF)";
  }

  deviation /oc-if:interfaces/oc-if:interface/oc-if:config/oc-if:name {
    deviate not-supported;
  }
  deviation /oc-if:interfaces/oc-if:interface/oc-if:config/oc-if:type {
    deviate not-supported;
  }

  deviation /oc-if:interfaces/oc-if:interface/oc-if:config/oc-if:loopback-mode {
    deviate not-supported;
  }
  deviation /oc-if:interfaces/oc-if:interface/oc-if:config/oc-if:enabled {
    deviate replace {
      type boolean;
      default "true";
    }
    description
      "This leaf contains the configured, desired state of the
      interface.

      Systems that implement the IF-MIB use the value of this
      leaf in the 'running' datastore to set
      IF-MIB.ifAdminStatus to 'up' or 'down' after an ifEntry
      has been initialized, as described in RFC 2863.

      Changes in this leaf in the 'running' datastore are
      reflected in ifAdminStatus, and if ifAdminStatus is
      changed via any other mechanism, this leaf will reflect that change.";
  }
  deviation /oc-if:interfaces/oc-if:interface/oc-if:config/oc-if:mtu {
    deviate replace {
      type uint32;
    }
    description
      "Set the max transmission unit size in octets
      for the physical interface.  If this is not set, the mtu is
      set to the operational default -- e.g., 1500 bytes on an
      Ethernet interface.";
  }
  deviation /oc-if:interfaces/oc-if:interface/oc-if:state/oc-if:enabled {
    deviate replace {
      type boolean;
      default "true";
      config "false";
    }
    description
      "This leaf contains the configured, desired state of the
      interface.
      
      Systems that implement the IF-MIB use the value of this
      leaf in the 'running' datastore to set
      IF-MIB.ifAdminStatus to 'up' or 'down' after an ifEntry
      has been initialized, as described in RFC 2863.

      Changes in this leaf in the 'running' datastore are
      reflected in ifAdminStatus, and if ifAdminStatus is
      changed via any other mechanism, this leaf will reflect that change.";
  }
  deviation /oc-if:interfaces/oc-if:interface/oc-if:state/oc-if:loopback-mode {
    deviate not-supported;
  }

  deviation /oc-if:interfaces/oc-if:interface/oc-if:state/oc-if:logical {
    deviate not-supported;
  }

  deviation /oc-if:interfaces/oc-if:interface/oc-if:state/oc-if:management {
    deviate not-supported;
  }

  deviation /oc-if:interfaces/oc-if:interface/oc-if:state/oc-if:cpu {
    deviate not-supported;
  }

  deviation /oc-if:interfaces/oc-if:interface/oc-if:state/oc-if:counters/oc-if:carrier-transitions {
    deviate not-supported;
  }

  deviation /oc-if:interfaces/oc-if:interface/oc-if:state/oc-if:counters/oc-if:last-clear {
    deviate not-supported;
  }

  deviation /oc-if:interfaces/oc-if:interface/oc-if:hold-time {
    deviate not-supported;
  }

  deviation /oc-if:interfaces/oc-if:interface/oc-if:subinterfaces {
    deviate not-supported;
  }

}
