module at-openconfig-interfaces-deviation {
  yang-version 1;
  namespace "http://alliedtelesis.com/ns/yang/at-openconfig-interfaces-deviation";
  prefix at-oc-if;

  import openconfig-interfaces {
    prefix oc-if;
  }

  import iana-if-type {
    prefix ianaift;
  }

  organization
    "Allied Telesis Labs Limited";

  contact
    "Allied Telesis Customer Support Group";

  description
    "This module contains deviation statements for the openconfig-interfaces module.";

  revision "2024-10-24" {
    description
      "Set the identityref of interface if:type to ianaift:iana-interface-type.
       The field config/type was changed from 'not supported' to a 'replace' making
       the field read only. This field is mandatory and used in 'when' clauses by
       other models augmenting the openconfig-interfaces model.
       Add patterns for interface name and description. These are fairly
       generic patterns, and for interface name in particular should not
       be taken as indicative of how valid interface names should be
       formatted. Change support for mtu variable to not-supported.";
  }

  revision "2023-07-10" {
    description
      "Initial revision";
    reference
      "RFC 6020: YANG - A Data Modeling Language for the
       Network Configuration Protocol (NETCONF)";
  }

  deviation /oc-if:interfaces/oc-if:interface/oc-if:config/oc-if:name {
    deviate not-supported;
  }
  deviation /oc-if:interfaces/oc-if:interface/oc-if:config/oc-if:description {
    deviate replace {
      type string {
        pattern "[ -~]{1,768}";
      }
    }
  }
  deviation /oc-if:interfaces/oc-if:interface/oc-if:config/oc-if:type {
    deviate replace {
      type identityref {
        base ianaift:iana-interface-type;
      }
      config false;
    }
  }

  deviation /oc-if:interfaces/oc-if:interface/oc-if:config/oc-if:loopback-mode {
    deviate not-supported;
  }
  deviation /oc-if:interfaces/oc-if:interface/oc-if:config/oc-if:mtu {
    deviate not-supported;
  }
  deviation /oc-if:interfaces/oc-if:interface/oc-if:state/oc-if:type {
    deviate replace {
        type identityref {
          base ianaift:iana-interface-type;
        }
    }
  }
  deviation /oc-if:interfaces/oc-if:interface/oc-if:state/oc-if:loopback-mode {
    deviate not-supported;
  }

  deviation /oc-if:interfaces/oc-if:interface/oc-if:state/oc-if:mtu {
    deviate not-supported;
  }
  deviation /oc-if:interfaces/oc-if:interface/oc-if:state/oc-if:logical {
    deviate not-supported;
  }

  deviation /oc-if:interfaces/oc-if:interface/oc-if:state/oc-if:management {
    deviate not-supported;
  }

  deviation /oc-if:interfaces/oc-if:interface/oc-if:state/oc-if:cpu {
    deviate not-supported;
  }

  deviation /oc-if:interfaces/oc-if:interface/oc-if:state/oc-if:counters/oc-if:carrier-transitions {
    deviate not-supported;
  }

  deviation /oc-if:interfaces/oc-if:interface/oc-if:state/oc-if:counters/oc-if:last-clear {
    deviate not-supported;
  }

  deviation /oc-if:interfaces/oc-if:interface/oc-if:name {
    deviate replace {
      type string {
        pattern "[a-z][a-z0-9.]+";
      }
    }
  }

  deviation /oc-if:interfaces/oc-if:interface/oc-if:hold-time {
    deviate not-supported;
  }

  deviation /oc-if:interfaces/oc-if:interface/oc-if:subinterfaces {
    deviate not-supported;
  }

}
