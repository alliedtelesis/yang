module at-arp-dos-mon {
  yang-version 1.1;

  namespace "http://alliedtelesis.com/ns/yang/at-arp-dos-mon";
  prefix at-arp-dos-mon;

  organization
    "Allied Telesis Labs New Zealand";

  contact
    "Allied Telesis Customer Support Group";

  description
    "This document defines a YANG module for
    Allied Telesis ARP denial of service monitoring";

  revision 2026-05-13 {
    description "Add ARP pps threshold.";
    reference "2026-05-13";
  }

  revision 2026-05-05 {
    description
      "Initial revision.";
    reference
      "RFC 6020: A Data Modeling Language for the
            Network Configuration Protocol (NETCONF)
       RFC 7950: The YANG 1.1 Data Modeling Language";
  }

  container arp-dos-mon {
    description
      "ARP denial of service monitoring configuration";

    container service {
      description
        "ARP denial of service monitoring service";

      leaf enable {
        type boolean;
        default "false";
        description
          "Enable ARP denial of service monitoring service";
      }
      leaf threshold {
        type uint16 {
          range "1..5000";
        }
        units "packets per second";
        default "100";
        description
          "ARP frame rate threshold in packets per second. When the incoming
           ARP rate on a monitored interface exceeds this value, the event
           is logged as a potential denial-of-service attack.";
      }
    }
  }
}
